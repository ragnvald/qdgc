FME workspace qdgc_generator.fmw

Parameters:
- SourceDataset_ESRISHAPE = $(FME_MF_DIR)spatial_source_files\ne_10m_admin_0_countries.shp   # Source Esri Shapefile(s)
- DestDataset_GEOPACKAGE = $(FME_MF_DIR)output\qdgc_all.gpkg   # GeoPackage File
- DestDataset_POSTGIS = qdgc_continents   # Connection

Readers:
- ESRISHAPE_1: ESRISHAPE from $(SourceDataset_ESRISHAPE)

Writers:
- GEOPACKAGE_1: GEOPACKAGE to $(DestDataset_GEOPACKAGE)
- POSTGIS_1: POSTGIS to $(DestDataset_POSTGIS)

ne_10m_admin_0_countries (reader ESRISHAPE_1)
    attributes: scalerank short, featurecla char(30), LABELRANK float, SOVEREIGNT char(32), SOV_A3 char(3), ADM0_DIF float, LEVEL float, TYPE char(17), ADMIN char(40), ADM0_A3 char(3), GEOU_DIF float, GEOUNIT char(40), GU_A3 char(3), SU_DIF float, SUBUNIT char(40), SU_A3 char(3), BRK_DIFF float, NAME char(36), NAME_LONG char(40), BRK_A3 char(3), BRK_NAME char(36), BRK_GROUP char(30), ABBREV char(13), POSTAL char(4), FORMAL_EN char(52), FORMAL_FR char(35), NOTE_ADM0 char(22), NOTE_BRK char(164), NAME_SORT char(36), NAME_ALT char(38),
      MAPCOLOR7 float, MAPCOLOR8 float, MAPCOLOR9 float, MAPCOLOR13 float, POP_EST double, GDP_MD_EST float, POP_YEAR float, LASTCENSUS float, GDP_YEAR float, ECONOMY char(26), INCOME_GRP char(23), WIKIPEDIA float, FIPS_10_ char(3), ISO_A2 char(5), ISO_A3 char(3), ISO_N3 char(3), UN_A3 char(4), WB_A2 char(3), WB_A3 char(3), WOE_ID float, WOE_ID_EH float, WOE_NOTE char(190), ADM0_A3_IS char(3), ADM0_A3_US char(3), ADM0_A3_UN float, ADM0_A3_WB float, CONTINENT char(23), REGION_UN char(23), SUBREGION char(25), REGION_WB char(26),
      NAME_LEN float, LONG_LEN float, ABBREV_LEN float, TINY float, HOMEPART float
    -> AttributeFilter
AttributeFilter
    ATTR_NAME = CONTINENT
    ATTR_VALUES = <Empty>,<Missing>,<Null>,<Unfiltered>,Africa
    Africa -> BoundingBoxAccumulator_2
BoundingBoxAccumulator_2
    ACCUM_ATTRS_NAME = Use Attributes From One Feature
    BOUNDING_BOX -> AttributeClassifier
AttributeClassifier
    CLASS = ASCII
    SRC_ATTR = ISO_A3
    PASSED -> AttributeRenamer
AttributeRenamer
    ATTR_TABLE = RENAME_SET_DEFAULT CONTINENT > code
    -> AttributeRemover
AttributeRemover
    REMOVE_ATTRS = continent,REGION_UN,SUBREGION,region_wb,wb_a2,brk_name,gu_a3,homepart,HOMEPART,iso_a2,region_un,NAME_LEN,su_a3,name_alt,adm0_a3_un,adm0_dif,LASTCENSUS,pop_est,abbrev,brk_group,GDP_YEAR,sovereignt,brk_a3,MAPCOLOR13,level,SUBUNIT,long_len,lastcensus,FORMAL_FR,UN_A3,CONTINENT,sov_a3,SU_DIF,iso_n3,name_long,formal_en,WOE_ID_EH,note_adm0,WIKIPEDIA,wb_a3,BRK_NAME,mapcolor9,NOTE_BRK,featurecla,geounit,subunit,ABBREV,FIPS_10_,NAME,BRK_A3,NAME_ALT,note_brk,subregion,BRK_DIFF,wikipedia,GEOUNIT,ISO_A3,POP_EST,gdp_md_est,GDP_MD_EST,POSTAL,un_a3,ISO_N3,REGION_WB,geou_dif,WB_A3,SU_A3,economy,ADM0_DIF,ECONOMY,NAME_LONG,income_grp,SOVEREIGNT,SOV_A3,woe_id,brk_diff,ADMIN,GU_A3,gdp_year,NAME_SORT,ADM0_A3_UN,LONG_LEN,ISO_A2,GEOU_DIF,TYPE,name_sort,LABELRANK,mapcolor7,TINY,formal_fr,type,INCOME_GRP,WOE_ID,ABBREV_LEN,abbrev_len,scalerank,adm0_a3_us,MAPCOLOR9,mapcolor13,ADM0_A3,ADM0_A3_WB,WOE_NOTE,mapcolor8,LEVEL,POP_YEAR,adm0_a3_is,pop_year,BRK_GROUP,MAPCOLOR8,FORMAL_EN,ADM0_A3_US,fips_10,postal,WB_A2,name_len,tiny,admin,labelrank,adm0_a3,adm0_a3_wb,su_dif,MAPCOLOR7,NOTE_ADM0,ADM0_A3_IS
    -> StringCaseChanger
StringCaseChanger
    ATTRCHOICE = Selected Attributes
    ATTRLIST = code
    CHANGE_TYPE = lowercase
    -> att_create_qdgc
att_create_qdgc: AttributeCreator
    ATTR_LIST = qdgc,FME_NULL_VALUE
    -> att_create_qdgc_level
att_create_qdgc_level: AttributeCreator
    ATTR_LIST = qdgc_level,7
    -> att_create_qdgc_cellsize_2
    -> att_create_qdgc_level_Output
att_create_qdgc_cellsize_2: AttributeCreator
    ATTR_LIST = qdgc_cellsize,@div(1,(@pow(2,@Value(qdgc_level))))
    -> AttributeRemover_3
AttributeRemover_3
    REMOVE_ATTRS = name
    -> BoundingBoxAccumulator
BoundingBoxAccumulator
    ACCUM_ATTRS_NAME = Use Attributes From One Feature
    GROUP_BY = code
    BOUNDING_BOX -> BoundsExtractor
    BOUNDING_BOX -> BoundingBoxAccumulator_BoundingBox
BoundsExtractor
    XMAX = _xmax
    XMIN = _xmin
    YMAX = _ymax
    YMIN = _ymin
    ZMAX = _zmax
    ZMIN = _zmin
    -> xmax_more_than_0
    -> xmax_less_than_0
    -> xmin_more_than_0
    -> xmin_less_than_0
    -> ymax_more_than_0
    -> ymax_less_than_0
    -> ymin_more_than_0
    -> ymin_less_than_0
xmax_more_than_0: Tester
    BOOL_OP = OR
    COMPOSITE_TEST = 1
    TEST_CLAUSE = TEST @Value(_xmax) >= 0
    TEST_MODE = TEST
    PASSED -> ExpressionEvaluator
ExpressionEvaluator
    ACTION = Overwrite Existing Attributes
    ATTRLIST = _xmax
    EXPRESSION = @Value(_xmax)+1
    -> Dissolver
xmax_less_than_0: Tester
    BOOL_OP = OR
    COMPOSITE_TEST = 1
    TEST_CLAUSE = TEST @Value(_xmax) <= 0
    TEST_MODE = TEST
    PASSED -> ExpressionEvaluator_2
ExpressionEvaluator_2
    ACTION = Overwrite Existing Attributes
    ATTRLIST = _xmax
    EXPRESSION = @Value(_xmax)-1
    -> Dissolver
xmin_more_than_0: Tester
    BOOL_OP = OR
    COMPOSITE_TEST = 1
    TEST_CLAUSE = TEST @Value(_xmin) >= 0
    TEST_MODE = TEST
    PASSED -> ExpressionEvaluator_3
ExpressionEvaluator_3
    ACTION = Overwrite Existing Attributes
    ATTRLIST = _xmin
    EXPRESSION = @Value(_xmin)+1
    -> Dissolver
xmin_less_than_0: Tester
    BOOL_OP = OR
    COMPOSITE_TEST = 1
    TEST_CLAUSE = TEST @Value(_xmin) <= 0
    TEST_MODE = TEST
    PASSED -> ExpressionEvaluator_4
ExpressionEvaluator_4
    ACTION = Overwrite Existing Attributes
    ATTRLIST = _xmin
    EXPRESSION = @Value(_xmin)-1
    -> Dissolver
ymax_more_than_0: Tester
    BOOL_OP = OR
    COMPOSITE_TEST = 1
    TEST_CLAUSE = TEST @Value(_ymax) >= 0
    TEST_MODE = TEST
    PASSED -> ExpressionEvaluator_5
ExpressionEvaluator_5
    ACTION = Overwrite Existing Attributes
    ATTRLIST = _ymax
    EXPRESSION = @Value(_ymax)+1
    -> Dissolver
ymax_less_than_0: Tester
    BOOL_OP = OR
    COMPOSITE_TEST = 1
    TEST_CLAUSE = TEST @Value(_ymax) <= 0
    TEST_MODE = TEST
    PASSED -> ExpressionEvaluator_6
ExpressionEvaluator_6
    ACTION = Overwrite Existing Attributes
    ATTRLIST = _ymax
    EXPRESSION = @Value(_ymax)+1
    -> Dissolver
ymin_more_than_0: Tester
    BOOL_OP = OR
    COMPOSITE_TEST = 1
    TEST_CLAUSE = TEST @Value(_ymin) >= 0
    TEST_MODE = TEST
    PASSED -> ExpressionEvaluator_7
ExpressionEvaluator_7
    ACTION = Overwrite Existing Attributes
    ATTRLIST = _ymin
    EXPRESSION = @Value(_ymin)+1
    -> Dissolver
ymin_less_than_0: Tester
    BOOL_OP = OR
    COMPOSITE_TEST = 1
    TEST_CLAUSE = TEST @Value(_ymin) <= 0
    TEST_MODE = TEST
    PASSED -> ExpressionEvaluator_8
ExpressionEvaluator_8
    ACTION = Overwrite Existing Attributes
    ATTRLIST = _ymin
    EXPRESSION = @Value(_ymin)+1
    -> Dissolver
Dissolver
    ACCUM_INPUT_ATTRS = Use Attributes From One Feature
    CLEANING_TOLERANCE = Automatic
    CONNECT_Z_MODE = First Wins
    DEAGGREGATE_INPUT = Yes
    GROUP_BY = code
    AREA -> Bufferer
Bufferer
    ANGLE = 22.5
    CAP_STYLE = Round
    CORNER_STYLE = Round
    MODE = AREA
    OFFSET = 1
    OFFSET_UNITS = NONE
    BUFFERED -> AttributeRemover_4
AttributeRemover_4
    -> BoundsExtractor_2
BoundsExtractor_2
    XMAX = _xmax
    XMIN = _xmin
    YMAX = _ymax
    YMIN = _ymin
    ZMAX = _zmax
    ZMIN = _zmin
    -> get_integer_degrees
get_integer_degrees: AttributeCreator
    ATTR_TABLE:
      SET_TO _xmin = @round(@Value(_xmin))
      SET_TO _xmax = @round(@Value(_xmax))
      SET_TO _ymin = @round(@Value(_ymin))
      SET_TO _ymax = @round(@Value(_ymax))
    -> makeboxesnotwar
makeboxesnotwar: 2DBoxReplacer
    MAXXVALATTR = @Value(_xmax)
    MAXYVALATTR = @Value(_ymax)
    MINXVALATTR = @Value(_xmin)
    MINYVALATTR = @Value(_ymin)
    BOX -> 2DGridAccumulator
2DGridAccumulator
    COL_ATTR = lon
    GRID_TYPE = Polygons
    GROUP_BY = code qdgc qdgc_cellsize qdgc_level
    ROW_ATTR = lat
    SIZE_TYPE = Cell Size
    STARTINGCORNER = Lower Left
    XINC = @Value(qdgc_cellsize)
    YINC = @Value(qdgc_cellsize)
    GRID -> AttributeRemover_2
    GRID -> 2DGridAccumulator_Grid
AttributeRemover_2
    REMOVE_ATTRS = lon,lat
    -> CenterPointExtractor
CenterPointExtractor
    CENTX = lon
    CENTY = lat
    EXTRACTIONMODE = CENTER
    -> AttributeCreator
AttributeCreator
    ATTR_TABLE = SET_TO areakm2 = 0
    -> StringPadder
StringPadder
    BLANK_ATTRIBUTE = Yes
    PADCHAR = 0
    SIDE = Left
    SRC_ATTRS = qdgc_level
    WIDTH = 2
    -> lonlat2qdgc
Note: Calculate QDGC-string from lon/lat and level
lonlat2qdgc: PythonCaller
    PYTHONSOURCE:
      #*******************************************************************
      # Longitude/Latitude to Quarter Degree Grid Cell standard conversion
      # utility
      #
      # The utility will accept the path of a .dbf-file as an argument. By
      # setting the QDGC level the script will use the LON/LAT values to
      # produce a QDGC string value which is inserted into the QDGC column
      # of the .dbf-file.
      #
      # Delivered as-is. If it works - fine for you. If it fails - too bad.
      # No are given guarantees whatsoever. If you use this program for
      # illegal purposes - don't blame me.
      #
      # License type is Gnu GPL. Copy, distribute and change freely. Keep
      # the author in mind for crediting. Come to think of it, use this
      # reference:
      #
      # R. Larsen, T. Holmern, S. D. Prager, H. Maliti and E. Roskaft
      #     (2009) Using the extended quarter degree grid cell system
      #     to unify mapping and sharing of biodiversity data, African
      #     Journal of Ecology. Volume 47, Issue 3 , Pages 382 - 392
      #
      # Author Ragnvald Larsen, Dept of Biology, NTNU (www.bio.ntnu.no)
      # ragnvald(at)mindland.com
      #
      # Version 0.6 (01.12.2009)


      #Math is used in this one
      import math
      import fmeobjects


      #*******************************************************************
      # Numerical representation of lat-lon
      #
      # Input: Longitude, Latitude
      # 38.98754324/-9.87548764
      #
      # Output: Absolute referense to degree square
      # E038S09?
      #
      def get_lonlat(lon_value,lat_value):

          #Put character in front of longitudal value
          if lon_value < 0:
              square = 'W'
          else:
              square = 'E'


          #Find absolute value for longitude
          lon_string=str(int(abs(lon_value)))


          #The longitudal value of the square is printed with three decimals
          square = square + (lon_string).zfill(3)



          #Put character in front of latitudal value
          if  lat_value < 0 :
              square = square + 'S'
          else:
              square = square + 'N'


          #find absolute value for latitude
          lat_string=str(int(abs(lat_value)))

          #find int lat. Remember that latitudes absolute values never excceed 90
          square = square + (lat_string).zfill(2)

          return square


      #*******************************************************************
      # RQDGC - recursive quarter degree grid cell
      #
      # Input: Latitude, Longitude, depth in powers of two, starting string
      # -9.87548764, 38.98754324, 5, ""
      #
      # Output: DDDBB
      #
      # Obs!: This function places origo in the cell in the upper left
      # in the southern hemisphere and in the lower left corner
      # in the norther hemisphere. Is this ok?
      def get_recursive_qdgc(lon_value,lat_value,depth,square):

          #remove all but the decimals (eg: 30.54 -> 0.54)
          #this also takes care of values below zero
          if  lon_value >1 :
              lon_value = lon_value - math.floor(lon_value)
          elif (lon_value<-1):
              lon_value = lon_value + abs(math.ceil(lon_value))

          #remove all but the decimals (eg: 30.54 -> 0.54)
          #this also takes care of values below zero
          if  (lat_value > 1):
              lat_value = lat_value - math.floor(lat_value)
          elif (lat_value<-1):
              lat_value = lat_value + abs(math.ceil(lat_value))


          #check which of the 4 squares the value fals within
          #Q1 - - - - - - - - - - - - - - - - - - - - - - - - - -
          if ((lon_value>=0) and (lat_value>=0)):

              #upper left - A
              if ((lon_value <0.5) and (lat_value>=0.5)):
                  square =  square + 'A'

                  lon_value=lon_value*2
                  lat_value=(lat_value-0.5)*2


              #upper right - B
              elif ((lon_value>=0.5) and (lat_value>=0.5)):
                  square = square + 'B'

                  lon_value=(lon_value-0.5)*2
                  lat_value=(lat_value-0.5)*2


              #lower left - C
              elif ((lon_value<0.5) and (lat_value<0.5)):
                  square = square + 'C'

                  #both values are doubled
                  lat_value=lat_value*2
                  lon_value=lon_value*2


              #lower right - D
              elif ((lon_value>=0.5) and (lat_value<0.5)):
                  square =  square + 'D'

                  lon_value=(lon_value-0.5)*2
                  lat_value=lat_value*2


          # Q2 - - - - - - - - - - - - - - - - - - - - - - - - - -
          elif ((lon_value>=0) and (lat_value<=0)):

              # upper left - A
              if ((lon_value <0.5) and (lat_value>-0.5)):
                  square = square + 'A'

                  lon_value=lon_value*2
                  lat_value=lat_value*2

              #upper right - B
              elif ((lon_value>=0.5) and (lat_value>-0.5)):
                  square = square + 'B'

                  lon_value=(lon_value-0.5)*2
                  lat_value=lat_value*2

              #lower left - C
              elif ((lon_value<0.5) and (lat_value<=-0.5)):
                  square = square + 'C'

                  lon_value=lon_value*2
                  lat_value=(lat_value+0.5)*2

              #lower right - D
              elif ((lon_value>=0.5) and (lat_value<=-0.5)):
                  square = square + 'D'

                  lon_value=(lon_value-0.5)*2
                  lat_value=(lat_value+0.5)*2


          # Q3 - - - - - - - - - - - - - - - - - - - - - - - - - -
          elif ((lon_value<=0) and (lat_value<=0)):

              #upper left - A
              if ((lon_value<=-0.5) and (lat_value>-0.5)):
                  square = square + 'A'

                  lon_value=(lon_value+0.5)*2
                  lat_value=lat_value*2

              #upper right - B
              elif ((lon_value>-0.5) and (lat_value>-0.5)):
                  square = square + 'B'

                  lon_value=lon_value*2
                  lat_value=lat_value*2

              #lower left - C
              elif ((lon_value<=-0.5) and (lat_value<=-0.5)):
                  square = square + 'C'

                  lon_value=(lon_value+0.5)*2
                  lat_value=(lat_value+0.5)*2

              #lower right - D
              elif ((lon_value>-0.5) and (lat_value<=-0.5)):
                  square = square + 'D'

                  lon_value=lon_value*2
                  lat_value=(lat_value+0.5)*2


          # Q4 - - - - - - - - - - - - - - - - - - - - - - - - - -
          elif ((lon_value<=0) and (lat_value>=0)):

              #upper left - A
              if ((lon_value <=-0.5) and (lat_value>=0.5)):
                  square = square + 'A'

                  lon_value=(lon_value+0.5)*2
                  lat_value=(lat_value-0.5)*2

              #upper right - B
              elif ((lon_value>-0.5) and (lat_value>=0.5)):
                  square = square + 'B'

                  lon_value=lon_value*2
                  lat_value=(lat_value-0.5)*2

              #lower left - C
              elif ((lon_value<=-0.5) and (lat_value<0.5)):
                  square = square + 'C'

                  lon_value=(lon_value+0.5)*2
                  lat_value=(lat_value)*2

              #lower right - D
              elif ((lon_value>-0.5) and (lat_value<0.5)):
                  square = square + 'D'

                  lon_value=lon_value*2
                  lat_value=lat_value*2



          #find square sting length
          length = len(square)

          #as long as string length does not meed criteria for depth - continue calculation
          #as an argument the curent square value is sent to the function. This is added in
          #subsequent calculations, and eventually the number for the length of the string
          #equals the number of the depth variable. That's when the job is done.
          if (length < depth):
              #Calculation is recursive - continue the good work
              square = get_recursive_qdgc(lon_value,lat_value,depth,square)

          #return value for square
          return square


      #This is where the program is executed

      def qdgc(feature):

          lon_value = feature.getAttribute('lon')
          lat_value = feature.getAttribute('lat')
          qdgc_level = int(feature.getAttribute('qdgc_level'))

          lonlatvalues = get_lonlat(lon_value,lat_value)

          qdgcvalues = get_recursive_qdgc(lon_value,lat_value,qdgc_level,"")

          resultstring = lonlatvalues + qdgcvalues

          feature.setAttribute('qdgc',resultstring)
    PYTHONSYMBOL = qdgc
    -> AttributeRenamer_2
AttributeRenamer_2
    ATTR_TABLE = RENAME_SET_DEFAULT code > continent
    -> att_create_qdgc_2
att_create_qdgc_2: AttributeCreator
    ATTR_TABLE = SET_TO tablename = tbl_qdgc_@Value(qdgc_level)_@Value(continent)
    -> Inspector
    -> ne_10m_admin_0_countries (writer POSTGIS_1)
Inspector
ne_10m_admin_0_countries (writer POSTGIS_1)
    attributes: continent varchar(23), qdgc varchar(200), qdgc_level int2, qdgc_cellsize float4, lon float4, lat float4, areakm2 float4
2DGridAccumulator_Grid: Inspector
BoundingBoxAccumulator_BoundingBox: Logger
    LOG_FEATURE = LOG_ONLY
    MAXCOORDS = 20
    MAXFEATS = 20
    MESSAGE = Feature is:
    SEVERITY = INFO
att_create_qdgc_level_Output: Inspector
